module pocnetconfschemaless {
    yang-version 1;
    namespace "urn:opendaylight:params:xml:ns:yang:pocnetconfschemaless";
    prefix "pocnetconfschemaless";

    revision "2017-03-17" {
        description "Initial revision of pocnetconfschemaless model";
    }

    rpc get-hostname {
        description "Get the hostname of a NETCONF network device";
        input {
            leaf node-id {
                type string;
                description "Node identifier of the NETCONF device";
            }
            leaf device-family {
                type string;
                description "The family of the NETCONF device to talk to the device.
                    Can be one of 'junos' or 'netconf-testtool'";
            }
        }
        output {
            leaf hostname {
                type string;
                description "hostname of the NETCONF device";
            }
        }
    }

    rpc set-hostname {
        description "Set the hostname of a NETCONF network device";
        input {
            leaf node-id {
                type string;
                description "Node identifier of the NETCONF device";
            }
            leaf device-family {
                type string;
                description "The family of the NETCONF device to talk to the device.
                    Can be one of 'junos' or 'netconf-testtool'";
            }
            leaf hostname {
                type string;
                description "New hostname of the NETCONF device";
            }
        }
    }
}
